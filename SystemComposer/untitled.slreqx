# untitled

## #3 (Informational)
Sensor type: INA219

## #4 (Functional)
Driver type: TB6612Fng
Vmax=12v
Imax=1.2A
Include Stanby Mode

## #5 (Functional)
DC with Hall Encoder
Vmax = 12V
Gear Ration =
PPR =

## #6 (Functional)
MEGA PRO 2560
Interrupt pin
PWM pin

## #7 (Functional)
Hall Encoder
Quadrature

## #8 (Functional)
Estimated all parameters using UKF with Recursive Least Square

## #9 (Functional)
Torque control using Cascade from of torque inner and speed outer loop

## #10 (Functional)
EKF with Recursive Least square
